module tl1-impl {
    yang-version 1;
    namespace "urn:opendaylight:params:xml:ns:yang:tl1:impl";
    prefix "tl1-impl";

    import config { prefix config; revision-date 2013-04-05; }
    import opendaylight-md-sal-binding { prefix md-sal-binding; revision-date 2013-10-28;}

    description
        "Service definition for tl1 project";

    revision "2014-12-10" {
        description
            "Initial revision";
    }

    identity tl1 {
        base config:module-type;
        config:java-name-prefix Tl1;
    }

    augment "/config:modules/config:module/config:configuration" {
        case tl1 {
            when "/config:modules/config:module/config:type = 'tl1'";
            container broker {
                uses config:service-ref {
                    refine type {
                        mandatory true;
                        config:required-identity md-sal-binding:binding-broker-osgi-registry;
                    }
                }
            }
            
            
//            container notification-service {
//                uses config:service-ref {
//                    refine type {
//                        mandatory true;
//                        config:required-identity md-sal-binding:binding-notification-service;
//                    }
//                }
//            }
        }
    }
}
