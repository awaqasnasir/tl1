module tl1 {
    yang-version 1;
    namespace "urn:opendaylight:params:xml:ns:yang:tl1";
    prefix "tl1";

    revision "2015-01-05" {
        description "Initial revision of tl1 model";
    }
   
    rpc add-device {
        input {
            leaf ip {
                type string;
            }
            leaf port {
                type string;
            }
        }
        output {
            leaf status {
            	type enumeration{
        			enum "success"{
        				value 0;
        				description "the ip added successfully";
        			}
        			enum "failed to connect"{
        				value 1;
        				description "could not add ip";
        			}
     		  }
            }
        }
    }
    
    // rpc to send command to single device
    rpc send-Tl1command-to-a-device {
        input {
        	leaf Verb {
                type string;
                description "verb for action to be performed";
            }
        	leaf Modeifier1 {
                type string;
                description "optional modifier for verb";
            }
            leaf Modeifier2 {
                type string;
                description "optional modifier for verb";
            }
            leaf TID {
                type string;
                description "id of targeted device";
            }
            leaf AID {
                type string;
                description "id of targeted device";
            }
            leaf CTAG {
                type string;
                description "id of targeted device";
            }
            leaf GeneralBlock {
                type string;
                description "id of targeted device";
            }
            leaf dataBlock-E {
                type string;
                description "id of targeted device";
            }
            leaf dataBlock-F {
                type string;
                description "id of targeted device";
            }
            leaf dataBlock-G {
                type string;
                description "id of targeted device";
            }
        }
        output {
            leaf CommandResponse {
                type string;
            }
        }
    }
    
    
//  rpc to send command to All device
    rpc send-Tl1command-to-all-device {
        input {
        	leaf Verb {
                type string;
                description "verb for action to be performed";
            }
        	leaf Modeifier1 {
                type string;
                description "optional modifier for verb";
            }
            leaf Modeifier2 {
                type string;
                description "optional modifier for verb";
            }
            leaf AID {
                type string;
                description "id of targeted device";
            }
            leaf CTAG {
                type string;
                description "id of targeted device";
            }
            leaf GeneralBlock {
                type string;
                description "id of targeted device";
            }
            leaf dataBlock-E {
                type string;
                description "id of targeted device";
            }
            leaf dataBlock-F {
                type string;
                description "id of targeted device";
            }
            leaf dataBlock-G {
                type string;
                description "id of targeted device";
            }
        }
        output {
            leaf-list Command-Responses {
                type string;
                description "responses from all devices";
            }
        }
    }
    
//  rpc to send command to multiple Device device
    rpc send-Tl1command-to-multiple-device {
        input {
        	leaf Verb {
                type string;
                description "verb for action to be performed";
            }
        	leaf Modeifier1 {
                type string;
                description "optional modifier for verb";
            }
            leaf Modeifier2 {
                type string;
                description "optional modifier for verb";
            }
            leaf-list TIDs {
                type string;
                description "Give ips for devices";
            }
            leaf AID {
                type string;
                description "id of targeted device";
            }
            leaf CTAG {
                type string;
                description "id of targeted device";
            }
            leaf GeneralBlock {
                type string;
                description "id of targeted device";
            }
            leaf dataBlock-E {
                type string;
                description "id of targeted device";
            }
            leaf dataBlock-F {
                type string;
                description "id of targeted device";
            }
            leaf dataBlock-G {
                type string;
                description "id of targeted device";
            }
        }
        output {
            leaf-list Command-Responses {
                type string;
                description "responses from multiple devices";
            }
        }
    }
    rpc reload-nodes {
        input {
        	leaf file-path {
                type string;
                description "path of file which contains ips and ports of network nodes";
            }
            
        }
        output {
            leaf result {
                type string;
            }
        }
    }
    
    
    container device-registry {
        list device-registry-entry {
        	key "ip";
            leaf ip {
                type string;
            }
            leaf port {
                type string;
            }
            
        }
    }
    
    
     
//    notification Device{
//    	leaf deviceStatu{
//    		type enumeration{
//    			enum "working"{
//    				value 0;
//    				description "the device is working properly";
//    			}
//    			enum "not_working"{
//    				value 1;
//    				description "the device is not working properly";
//    			}
//    		}
//    	}
//    }
    
    /*rpc hello-tl1 {
    input {
    	leaf ip {
            type string;
            description "Initial revision of tl1 model";
        }
        leaf message {
            type string;
        }
    }
    output {
        leaf greeting {
            type string;
        }
    }
}*/
}
